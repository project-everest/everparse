-- Differential testing: restricted character string types.
-- F* translation: src/ASN1/ASN1.DiffTest.Strings.fst
DiffStrings DEFINITIONS ::= BEGIN

Utf8 ::= UTF8String
Numeric ::= NumericString
Printable ::= PrintableString
Ia5 ::= IA5String
Visible ::= VisibleString
Bmp ::= BMPString
Universal ::= UniversalString
Teletex ::= TeletexString

END
