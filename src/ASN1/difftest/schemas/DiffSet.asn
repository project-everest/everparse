-- Differential testing: SET { ... } (X.690 10.3 canonical order).
-- F* translation: src/ASN1/ASN1.DiffTest.Set.fst
DiffSet DEFINITIONS ::= BEGIN

Set ::= SET {
  a [0] IMPLICIT INTEGER,
  b [1] IMPLICIT BOOLEAN OPTIONAL,
  c OCTET STRING
}

END
