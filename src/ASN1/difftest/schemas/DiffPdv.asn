-- Differential testing: EMBEDDED PDV (separate module, as not every
-- implementation supports it).
-- F* translation: src/ASN1/ASN1.DiffTest.Presentation.fst
DiffPdv DEFINITIONS ::= BEGIN

Pdv ::= EMBEDDED PDV

END
