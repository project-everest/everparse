-- Differential testing: VideotexString (separate module, as not every
-- implementation supports it).
-- F* translation: ../ASN1.DiffTest.Strings.fst
DiffVideotex DEFINITIONS ::= BEGIN

Videotex ::= VideotexString

END
