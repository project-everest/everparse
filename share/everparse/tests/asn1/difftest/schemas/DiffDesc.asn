-- Differential testing: ObjectDescriptor (separate module, as not every
-- implementation supports it).
-- F* translation: ../ASN1.DiffTest.Prim.fst
DiffDesc DEFINITIONS ::= BEGIN

Desc ::= ObjectDescriptor

END
