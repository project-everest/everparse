-- Differential testing: CHARACTER STRING (separate module, as not every
-- implementation supports it).
-- F* translation: ../ASN1.DiffTest.Presentation.fst
DiffCharStr DEFINITIONS ::= BEGIN

CharStr ::= CHARACTER STRING

END
