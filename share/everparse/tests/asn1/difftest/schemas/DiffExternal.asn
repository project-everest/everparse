-- Differential testing: EXTERNAL (separate module, as not every
-- implementation supports it).
-- F* translation: ../ASN1.DiffTest.Presentation.fst
DiffExternal DEFINITIONS ::= BEGIN

Ext ::= EXTERNAL

END
