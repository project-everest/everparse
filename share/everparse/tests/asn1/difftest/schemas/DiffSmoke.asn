-- Differential testing, walking-skeleton schema.
-- F* translation: ../ASN1.DiffTest.Smoke.fst
DiffSmoke DEFINITIONS IMPLICIT TAGS ::= BEGIN

Smoke ::= SEQUENCE {
  a INTEGER,
  b BOOLEAN OPTIONAL,
  c OCTET STRING
}

END
