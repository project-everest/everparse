-- Differential testing: EMBEDDED PDV (separate module, as not every
-- implementation supports it).
-- F* translation: ../ASN1.DiffTest.Presentation.fst
DiffPdv DEFINITIONS ::= BEGIN

Pdv ::= EMBEDDED PDV

END
